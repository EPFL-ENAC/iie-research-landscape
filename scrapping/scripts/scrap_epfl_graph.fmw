FME workspace scrap_epfl_graph.fmw

Parameters:
- SourceDataset_CSV2 = $(FME_MF_DIR)Nodes_N_Unit_202305121618.csv   # Source CSV (Comma Separated Value) File(s)
- SourceDataset_CSV2_5 = $(FME_MF_DIR)Edges_N_Unit_N_Concept_T_Research_202305121624.csv   # Source CSV (Comma Separated Value) File(s)
- SourceDataset_CSV2_4 = $(FME_MF_DIR)Nodes_N_Concept_202305121620.csv   # Source CSV (Comma Separated Value) File(s)

Readers:
- CSV2_1: CSV2 from $(SourceDataset_CSV2)
- CSV2_2: CSV2 from $(SourceDataset_CSV2_5)
- CSV2_3: CSV2 from $(SourceDataset_CSV2_4)

CSV (reader CSV2_2)
    attributes: UnitID varchar(13), PageID uint32, Score real32, EdgeID varchar(22), MD5CheckSum varchar(33)
    -> TestFilter
    -> BulkAttributeRenamer
BulkAttributeRenamer
    ATTRCHOICE = All Attributes
    MODE_CHOICE = RENAME
    PATTERN_ACTION_DISP = ADDPREFIX
    REPLACE_STR = edge_
    -> FeatureMerger [SUPPLIER]
TestFilter
    DEFAULT_VALUE = <UNFILTERED>
    PASSED_TEST_GROUP_OUTPUT = FIRST
    TEST_LIST = "BOOL_OP,OR,COMPOSITE_TEST,""""""1"""""",TEST_CLAUSE,TEST @Value(Score) > 5",@Value(Score) > 5
CSV (reader CSV2_1)
    attributes: UnitID varchar(19), UnitInitials varchar(19), UnitType varchar(16), UnitName varchar(98), UnitNameFr varchar(98), UnitNameEn varchar(89), UnitShortName varchar(50), UnitPath varchar(58), UnitPathDepth uint32, UnitCreated date, UnitTerminated date, PrimaryLanguage varchar(4), IsEPFLUnit uint32, IsTemporary uint32, NumericID uint32, ParentNumericID uint32, NodeID varchar(19), MD5CheckSum varchar(33)
    -> Tester
Tester
    BOOL_OP = OR
    TEST_CLAUSE = CASE_INSENSITIVE_TEST @Value(UnitPath) BEGINS_WITH EPFL > ENAC > IIE >
    TEST_MODE = CASE_INSENSITIVE_TEST
    PASSED -> FeatureMerger [REQUESTOR]
    PASSED -> AttributeKeeper
FeatureMerger
    ATTR_ACCUM_MODE = Merge Supplier
    ATTR_CONFLICT_RES = Use Requestor
    IGNORE_NULLS = No
    JOIN_KEYS = @Value(UnitID) @Value(edge_UnitID) AUTO
    LIST_ATTRS_TO_INCLUDE = edge_EdgeID edge_PageID edge_Score
    LIST_NAME = egde
    MERGE_TYPE = Attributes Only
    PROCESS_DUPS = NO
    REJECT_NULL_MISSING_KEYS = No
    SUPPLIERS_FIRST = No
    MERGED -> Counter
Counter
    CNT_ATTR = _count
    DOMAIN = counter
    SCOPE = Global
    START = 0
    -> AttributeRemover
    -> FeatureMerger_3 [REQUESTOR]
AttributeRemover
    REMOVE_ATTRS = IsEPFLUnit,IsTemporary,MD5CheckSum,NodeID,NumericID,ParentNumericID,PrimaryLanguage,UnitCreated,UnitID,UnitInitials,UnitName,UnitNameEn,UnitNameFr,UnitPath,UnitPathDepth,UnitShortName,UnitTerminated,UnitType,edge_EdgeID,edge_MD5CheckSum,edge_PageID,edge_Score,edge_UnitID
    -> ListExploder
ListExploder
    ATTR_ACCUM_MODE = Merge List Attributes
    ATTR_CONFLICT_RES = Use List Attribute Values
    INDEX_ATTR = _element_index
    LIST_ATTR = egde{}
    ELEMENTS -> FeatureMerger_2 [REQUESTOR]
AttributeKeeper
    CREATE_BULK_MODE_FEATURES = NO
    KEEP_ATTRS = UnitID,UnitPath
CSV (reader CSV2_3)
    attributes: PageID uint32, PageIDFr uint32, PageTitle varchar(62), PageTitleFr varchar(89), PageTitleDisplay varchar(62), PageTitleFrDisplay varchar(89), PageContent varchar(159289), PageContentFr varchar(286085), DegreeScore real32, NodeID uint32, MD5CheckSum varchar(33)
    -> FeatureMerger_2 [SUPPLIER]
FeatureMerger_2
    ATTR_ACCUM_MODE = Merge Supplier
    ATTR_CONFLICT_RES = Use Requestor
    IGNORE_NULLS = No
    JOIN_KEYS = @Value(edge_PageID) @Value(PageID) AUTO
    MERGE_TYPE = Attributes Only
    PROCESS_DUPS = NO
    REJECT_NULL_MISSING_KEYS = No
    SUPPLIERS_FIRST = No
    MERGED -> AttributeManager
AttributeManager
    ATTR_TABLE:
      REMOVE edge_PageID
      REMOVE edge_EdgeID
      REMOVE _element_index
      REMOVE PageID
      REMOVE PageIDFr
      REMOVE PageContent
      REMOVE PageContentFr
      REMOVE NodeID
      REMOVE MD5CheckSum
    -> FeatureMerger_3 [SUPPLIER]
FeatureMerger_3
    ATTR_ACCUM_MODE = Merge Supplier
    ATTR_CONFLICT_RES = Use Requestor
    IGNORE_NULLS = No
    JOIN_KEYS = @Value(_count) @Value(_count) AUTO
    LIST_ATTRS_TO_INCLUDE = PageTitle PageTitleDisplay PageTitleFr PageTitleFrDisplay DegreeScore edge_Score
    LIST_NAME = concept
    MERGE_TYPE = Attributes Only
    PROCESS_DUPS = NO
    REJECT_NULL_MISSING_KEYS = No
    SUPPLIERS_FIRST = No
    MERGED -> AttributeRemover_2
AttributeRemover_2
    LIST_ATTRS = egde{}.edge_EdgeID egde{}.edge_PageID egde{}.edge_Score
    REMOVE_ATTRS = IsEPFLUnit,IsTemporary,MD5CheckSum,NodeID,NumericID,PageTitle,PageTitleDisplay,PageTitleFr,PageTitleFrDisplay,ParentNumericID,PrimaryLanguage,UnitCreated,UnitTerminated,_count,edge_EdgeID,edge_MD5CheckSum,edge_PageID,edge_UnitID,UnitPathDepth,UnitType,DegreeScore
    -> AttributeCreator
AttributeCreator
    ATTR_TABLE = SET_TO concept
    -> PythonCaller
    -> ListExploder_2
ListExploder_2
    ATTR_ACCUM_MODE = Merge List Attributes
    ATTR_CONFLICT_RES = Use List Attribute Values
    INDEX_ATTR = _element_index
    LIST_ATTR = concept{}
    ELEMENTS -> FeatureWriter_2 [Elements]
FeatureWriter_2
    CSV2_COORDINATE_SYSTEM_GRANULARITY = FEATURE_TYPE
    CSV2_DELIMITER = ,
    CSV2_ENCODING = UTF-8
    CSV2_EXISTING_FILE_HANDLING = Yes
    CSV2_EXTENSION = csv
    CSV2_FIELD_QUALIFIER_CHARACTER = "
    CSV2_FIELD_QUALIFIER_ESCAPE_CHARACTER = "
    CSV2_QUALIFY_FIELD_NAMES = if_needed
    CSV2_QUALIFY_FIELD_VALUES = if_needed
    CSV2_ROW_TERMINATION = System
    CSV2_TREAT_EMBEDDED_FIELD_QUALIFIERS_AS_UNSAFE = Yes
    CSV2_WRITE_BOM_FOR_UNICODE = Yes
    CSV2_WRITE_FIELD_NAMES = firstrow
    CSV2_WRITE_SCHEMA_FILE = NO
    DATASET = C:\projects\IIE\data
    DATASET_ATTR = _dataset
    FEATURE_TYPE_LIST_ATTR = _feature_types
    FORMAT = CSV2
    TOTAL_FEATURES_WRITTEN_ATTR = _total_features_written
PythonCaller
    PYTHONSOURCE:
      import fme
      import fmeobjects
      import json

      class FeatureProcessor(object):
          """Template Class Interface:
          When using this class, make sure its name is set as the value of the 'Class
          to Process Features' transformer parameter.
          """

          def __init__(self):
              """Base constructor for class members."""
              pass

          def input(self, feature):

              list_out = []

              for i,v in enumerate(feature.getAttribute('concept{}.PageTitle')) :
                  print(i)
                  _i = str(i)
                  out_dict = dict()
                  out_dict["PageTitle"] = feature.getAttribute('concept{'+_i+'}.PageTitle')
                  out_dict["PageTitleDisplay"] = feature.getAttribute('concept{'+_i+'}.PageTitleDisplay')
                  out_dict["PageTitleFr"] = feature.getAttribute('concept{'+_i+'}.PageTitleFr')
                  out_dict["PageTitleFrDisplay"] = feature.getAttribute('concept{'+_i+'}.PageTitleFrDisplay')
                  out_dict["DegreeScore"] = feature.getAttribute('concept{'+_i+'}.DegreeScore')
                  out_dict["edge_Score"] = feature.getAttribute('concept{'+_i+'}.edge_Score')





                  list_out.append(out_dict)



              feature.setAttribute('concept',json.dumps(list_out))




              """This method is called for each FME Feature entering the
              PythonCaller. If knowledge of all input Features is not required for
              processing, then the processed Feature can be emitted from this method
              through self.pyoutput(). Otherwise, the input FME Feature should be
              cached to a list class member and processed in process_group() when
              'Group by' attributes(s) are specified, or the close() method.

              :param fmeobjects.FMEFeature feature: FME Feature entering the
                  transformer.
              """
              self.pyoutput(feature)

          def close(self):
              """This method is called once all the FME Features have been processed
              from input().
              """
              pass

          def process_group(self):
              """When 'Group By' attribute(s) are specified, this method is called
              once all the FME Features in a current group have been sent to input().

              FME Features sent to input() should generally be cached for group-by
              processing in this method when knowledge of all Features is required.
              The resulting Feature(s) from the group-by processing should be emitted
              through self.pyoutput().

              FME will continue calling input() a number of times followed
              by process_group() for each 'Group By' attribute, so this
              implementation should reset any class members for the next group.
              """
              pass

          def has_support_for(self, support_type):
              """This method returns whether this PythonCaller supports a certain type.
              The only supported type is fmeobjects.FME_SUPPORT_FEATURE_TABLE_SHIM.

              :param int support_type: The support type being queried.
              :returns: True if the passed in support type is supported.
              :rtype: bool
              """
              if support_type == fmeobjects.FME_SUPPORT_FEATURE_TABLE_SHIM:
                  # If this is set to return True, FME will pass features to the input() method that
                  # come from a feature table object. This allows for significant performance gains
                  # when processing large numbers of features.
                  # To enable this, the following conditions must be met:
                  #   1) features passed into the input() method cannot be copied or cached for later use
                  #   2) features cannot be read or modified after being passed to self.pyoutput()
                  #   3) Group Processing must not be enabled
                  # Violations will cause undefined behavior.
                  return False

              return False
    PYTHONSYMBOL = FeatureProcessor
    -> FeatureWriter [Output]
FeatureWriter
    DATASET = $(FME_MF_DIR_ENCODED)extract_graph.json
    DATASET_ATTR = _dataset
    FEATURE_TYPE_LIST_ATTR = _feature_types
    FORMAT = JSON
    JSON_DESTINATION_DATASETTYPE_VALIDATION = Yes
    JSON_INDENT_SIZE = 0
    JSON_MAX_COORDINATE_PRECISION = 10
    JSON_PRETTY_PRINT = YES
    JSON_WRITER_CHARSET = UTF-8
    JSON_WRITE_BOM = No
    JSON_WRITE_FEATURE_TYPE_KEY = NO
    JSON_WRITE_GEOMETRY = NO
    TOTAL_FEATURES_WRITTEN_ATTR = _total_features_written
